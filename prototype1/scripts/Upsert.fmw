FME workspace Upsert.fmw

Creator
    GEOMTYPE = Geometry Object
    NUM = 1
    CREATED -> FeatureReader [INITIATOR]
FeatureReader
    ATTRIBUTES = "BBL Objekt","objectid,bbl_techplz,bbl_we,bbl_teilobj,bbl_bezeichnung,adr_land,adr_region,adr_ort,adr_plz,adr_strasse,adr_hausnr,adr_concat,av_egid,av_egrid,bbl_status,bbl_eigentm_art,bbl_objstrat,bbl_mietem,bbl_gbauj,bbl_verkaufsjahr,bbl_portfolio,bbl_portfolio_grp,bbl_anschwrt,bbl_buchwrt,bbl_gbdart1,bbl_gbdart2,bfs_gklas,bfs_gkat,bbl_objverantw,bbl_prtfverantw,garea_gf,garea_gfog,garea_gfug,garea_source,garea_ngf,garea_nf,garea_hnf,garea_nnf,garea_ff,garea_vf,garea_ebf,gvol_gv,gvol_gvog,gvol_gvug,gvol_source,gastw,gastw_og,gastw_ug,gastw_source,larea_ggf,larea_gsf,larea_uf,larea_source,av_bauzn_bez,av_bauzn_nutz,globalid,ao_id,ao_source,label,search,url_googlemaps,url_gwr,url_oreb,globalid_1,x,y,wg84_lon,wg84_lat"
    ATTR_ACCUM_MODE = Only Use Result
    CLIP_TO_ENVELOPE = NO
    COMBINE_GEOM = Use Result
    DATASET = D:\BBL_Gebäude.xlsx
    FORMAT = XLSXR
    GEOMETRY_TYPES = "BBL Objekt",""",fme_point"""
    INITIATOR_FIRST_OUTPUT = default
    INTERACT = NONE
    ORDER_RESULTS = No
    OUTPUT_ADD_SCHEMA_ATTRIBUTES = NO
    OUTPUT_FEATURES_DISPLAY = Schema and Data Features
    XLSXR_ALLOW_DOLLAR_SIGNS = YES
    XLSXR_APPLY_FILTERS = No
    XLSXR_CASE_SENSITIVE_FEATURE_TYPES = YES
    XLSXR_CREATE_FEATURE_TABLES_FROM_DATA = Yes
    XLSXR_EXCEL_COL_NAMES = YES
    XLSXR_EXPANDED_DATES_SCANNING = No
    XLSXR_EXPAND_MERGED_CELLS = Yes
    XLSXR_FORCE_DATETIME = NO
    XLSXR_QUERY_FEATURE_TYPES_FOR_MERGE_FILTERS = Yes
    XLSXR_READ_BLANK_AS = Null
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA_HANDLING_REVISION = 2
    XLSXR_SKIP_EMPTY_ROWS = YES
    XLSXR_STRIP_SHEETNAME_SPACES = YES
    XLSXR_TRIM_ATTR_NAME_WHITESPACE = Yes
    XLSXR_USE_CUSTOM_SCHEMA = NO
    BBL Objekt -> BulkAttributeRenamer
BulkAttributeRenamer
    ATTRCHOICE_ACTION = NONPROTECTEDFME
    MODE_CHOICE = RENAME
    PATTERN_ACTION_DISP = ADDPREFIX
    REPLACE_STR = gis_
    ATTRCHOICE = All Attributes
    -> TestFilter
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(gis_bbl_bezeichnung) CONTAINS ABGA",@Value(gis_bbl_bezeichnung) CONTAINS ABGA,"BOOL_OP,OR,COMPOSITE_TEST,""""""1"""""",TEST_CLAUSE,CASE_INSENSITIVE_TEST @Value(gis_bbl_bezeichnung) CONTAINS LÖVM",@Value(gis_bbl_bezeichnung) CONTAINS LÖVM,"BOOL_OP,OR,COMPOSITE_TEST,""""""1"""""",TEST_CLAUSE,TEST gis_bbl_bezeichnung NOT_ATTRIBUTE_HAS_A_VALUE """,gis_bbl_bezeichnung NOT_ATTRIBUTE_HAS_A_VALUE,"BOOL_OP,OR,COMPOSITE_TEST,""""""1"""""",TEST_CLAUSE,TEST @Value(gis_adr_land) NOT_= Schweiz",@Value(gis_adr_land) NOT_= Schweiz,"BOOL_OP,OR,COMPOSITE_TEST,""""""1"""""",TEST_CLAUSE,CASE_INSENSITIVE_TEST @Value(gis_bbl_techplz) CONTAINS GR",@Value(gis_bbl_techplz) CONTAINS GR
    <UNFILTERED> -> AttributeCreator
AttributeCreator
    ATTR_TABLE:
      SET_TO id (varchar(200)) = @Value(gis_bbl_techplz)
      SET_TO name (varchar(200)) = @Value(gis_bbl_bezeichnung)
      SET_TO portfolio (varchar(200)) = @Value(gis_bbl_portfolio)
      SET_TO in_gwr (varchar(4)) = TRUE
      SET_TO country (varchar(200)) = { "sap": "@Value(gis_adr_land)", "gwr": "", "korrektur": "", "match": true }
      SET_TO kanton (varchar(200)) = { "sap": "@Value(gis_adr_region)", "gwr": "", "korrektur": "", "match": true }
      SET_TO gemeinde (varchar(56)) = { "sap": "", "gwr": "", "korrektur": "", "match": true }
      SET_TO bfsNr (varchar(56)) = { "sap": "", "gwr": "", "korrektur": "", "match": true }
      SET_TO plz (varchar(200)) = { "sap": "@Value(gis_adr_plz)", "gwr": "", "korrektur": "", "match": true }
      SET_TO ort (varchar(200)) = { "sap": "@Value(gis_adr_ort)", "gwr": "", "korrektur": "", "match": true }
      SET_TO strasse (varchar(200)) = { "sap": "@Value(gis_adr_strasse)", "gwr": "", "korrektur": "", "match": true }
      SET_TO hausnummer (varchar(200)) = { "sap": "@Value(gis_adr_hausnr)", "gwr": "", "korrektur": "", "match": true }
      SET_TO zusatz (varchar(56)) = { "sap": "", "gwr": "", "korrektur": "", "match": true }
      SET_TO egid (varchar(200)) = { "sap": "@Value(gis_av_egid)", "gwr": "@Value(gis_av_egid)", "korrektur": "", "match": true }
      SET_TO egrid (varchar(200)) = { "sap": "@Value(gis_av_egrid)", "gwr": "", "korrektur": "", "match": true }
      SET_TO map_lat (varchar(200)) = @Value(gis_wg84_lat)
      SET_TO map_lng (varchar(200)) = @Value(gis_wg84_lon)
      SET_TO confidence (varchar(125)) = { "lage": 0, "total": 0, "adresse": 0, "bemessungen": 0, "identifikation": 0, "klassifikation": 0 }
      SET_TO lat (varchar(200)) = { "sap": "@Value(map_lat)", "gwr": "", "korrektur": "", "match": false }
      SET_TO lng (varchar(200)) = { "sap": "@Value(gis_wg84_lon)", "gwr": "", "korrektur": "", "match": false }
    -> AttributeRemover
AttributeRemover
    REMOVE_ATTRS = gis_adr_concat,gis_adr_hausnr,gis_adr_land,gis_adr_ort,gis_adr_plz,gis_adr_region,gis_adr_strasse,gis_ao_id,gis_ao_source,gis_av_bauzn_bez,gis_av_bauzn_nutz,gis_av_egid,gis_av_egrid,gis_bbl_anschwrt,gis_bbl_bezeichnung,gis_bbl_buchwrt,gis_bbl_eigentm_art,gis_bbl_gbauj,gis_bbl_gbdart1,gis_bbl_gbdart2,gis_bbl_mietem,gis_bbl_objstrat,gis_bbl_objverantw,gis_bbl_portfolio,gis_bbl_portfolio_grp,gis_bbl_prtfverantw,gis_bbl_status,gis_bbl_techplz,gis_bbl_teilobj,gis_bbl_verkaufsjahr,gis_bbl_we,gis_bfs_gkat,gis_bfs_gklas,gis_garea_ebf,gis_garea_ff,gis_garea_gf,gis_garea_gfog,gis_garea_gfug,gis_garea_hnf,gis_garea_nf,gis_garea_ngf,gis_garea_nnf,gis_garea_source,gis_garea_vf,gis_gastw,gis_gastw_og,gis_gastw_source,gis_gastw_ug,gis_globalid,gis_globalid_1,gis_gvol_gv,gis_gvol_gvog,gis_gvol_gvug,gis_gvol_source,gis_label,gis_larea_ggf,gis_larea_gsf,gis_larea_source,gis_larea_uf,gis_objectid,gis_search,gis_url_googlemaps,gis_url_gwr,gis_url_oreb,gis_wg84_lat,gis_wg84_lon,gis_x,gis_y
    -> FeatureWriter [Output]
Note: Upsert
FeatureWriter
    DATASET = Supabase Geo-Check
    DATASET_ATTR = _dataset
    FEATURE_TYPE_LIST_ATTR = _feature_types
    FORMAT = POSTGIS
    POSTGIS_ALWAYS_CREATE_FEATURE_TYPES = NO
    POSTGIS_BULK_COPY = YES
    POSTGIS_CASE_CONTROL_ATTR_NAMES = lower
    POSTGIS_CASE_CONTROL_FT_NAMES = none
    POSTGIS_COORDINATE_SYSTEM_GRANULARITY = FEATURE_TYPE
    POSTGIS_GENERIC_GEOMETRY = yes
    POSTGIS_NAMED_CONNECTION = Supabase Geo-Check
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
